FME workspace ExtraireDoublonsGPSTime.fmw

Parameters:
- DestDataset_LAS_6 = S:\Commun\SIG3D\2020\PROJETS_2020\20019_LIDAR_2020\03_REALISATION\01_CONTROLES\CONTROLE_ECHANTILLON_JUILLET\UNICITY\uniques   # Destination ASPRS LAS Folder
- DestDataset_LAS_5 = S:\Commun\SIG3D\2020\PROJETS_2020\20019_LIDAR_2020\03_REALISATION\01_CONTROLES\CONTROLE_ECHANTILLON_JUILLET\UNICITY\doublonGPS   # Destination ASPRS LAS Folder
- SourceDataset_LAS_2 = S:\Commun\SIG3D\2020\PROJETS_2020\20019_LIDAR_2020\03_REALISATION\01_CONTROLES\CONTROLE_ECHANTILLON_JUILLET\LIDAR_ECHANTILLON_ORIGINAL\2047000_7285000\2047000_7285000_Lidar2020.laz   # Source ASPRS LAS File(s)
- DestDataset_LAS = S:\Commun\SIG3D\2020\PROJETS_2020\20019_LIDAR_2020\03_REALISATION\01_CONTROLES\CONTROLE_ECHANTILLON_JUILLET\UNICITY\doublonGeom   # Destination ASPRS LAS Folder

Readers:
- LAS_1: LAS from $(SourceDataset_LAS_2) in EPSG:3948

Writers:
- LAS_2: LAS to $(DestDataset_LAS_6) in EPSG:3948
- LAS_3: LAS to $(DestDataset_LAS_5) in EPSG:3948
- LAS_4: LAS to $(DestDataset_LAS) in EPSG:3948

LAS (reader LAS_1)
    -> PointCloudCoercer
PointCloudCoercer
    ACCUM_ATTRS_NAME = Yes
    CONVERT_TO_DISPLAY = Individual Points
    PART_NUMBER_ATTR_NAME = _part_number
    POINT_COMPONENTS = gps_time intensity classification return number_of_returns angle scan_direction point_source_id
    POINT_COMPONENTS_PRESERVE_DISPLAY = Measures
    COERCED -> MeasureExtractor
    COERCED -> CoordinateExtractor
MeasureExtractor
    GEOM_TYPE = Point
    MEASURE_ATTR = gps_time
    MEASURE_NAME = gps_time
    -> MeasureExtractor_2
MeasureExtractor_2
    GEOM_TYPE = Point
    MEASURE_ATTR = return
    MEASURE_NAME = return
    -> DuplicateFilter
DuplicateFilter
    INPUT_ORDERED_CHOICE = No
    KEYATTR = gps_time return
    UNIQUE -> PointCloudCombiner
    DUPLICATE -> PointCloudCombiner_3
PointCloudCombiner
    ACCUM_ATTRS_NAME = Yes
    EXTRACT_RASTER_NODATA_NAME = No
    MEASURES_TO_PRESERVE = gps_time,Real64,intensity,UInt32,classification,Int16,return,Int16,number_of_returns,Int16,angle,UInt32,scan_direction,UInt32,point_source_id,Int16
    SPACING = 1.0
    -> Ligne31_unique (writer LAS_2)
Ligne31_unique (writer LAS_2)
PointCloudCombiner_3
    ACCUM_ATTRS_NAME = Yes
    EXTRACT_RASTER_NODATA_NAME = No
    MEASURES_TO_PRESERVE = gps_time,Real64,intensity,UInt32,classification,Int16,return,Int16,number_of_returns,Int16,angle,UInt32,scan_direction,UInt32,point_source_id,Int16
    SPACING = 1.0
    -> Ligne31_duplique (writer LAS_3)
Ligne31_duplique (writer LAS_3)
CoordinateExtractor
    IND = 0
    MODE = Specify Coordinate
    X_ATTR = _x
    Y_ATTR = _y
    Z_ATTR = _z
    -> DuplicateFilter_2
DuplicateFilter_2
    INPUT_ORDERED_CHOICE = No
    KEYATTR = _z _x _y
    DUPLICATE -> PointCloudCombiner_2
PointCloudCombiner_2
    ACCUM_ATTRS_NAME = Yes
    EXTRACT_RASTER_NODATA_NAME = No
    MEASURES_TO_PRESERVE = gps_time,Real64,intensity,UInt32,classification,Int16,return,Int16,number_of_returns,Int16,angle,UInt32,scan_direction,UInt32,point_source_id,Int16
    SPACING = 1.0
    -> LAS (writer LAS_4)
LAS (writer LAS_4)
