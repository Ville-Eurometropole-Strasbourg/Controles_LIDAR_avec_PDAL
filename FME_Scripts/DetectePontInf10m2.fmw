FME workspace DetectePontInf10m2.fmw

Parameters:
- SourceDataset_SQLITE3FDO = S:\Commun\SIG3D\2020\PROJETS_2020\20019_LIDAR_2020\03_REALISATION\01_CONTROLES\CONTROLE_ECHANTILLON_JUILLET\PONTS\2047000_7273000_ContourPont.sqlite   # SQLite3 Spatial (FDO) Database
- DestDataset_ESRISHAPE = S:\Commun\SIG3D\2020\PROJETS_2020\20019_LIDAR_2020\03_REALISATION\01_CONTROLES\CONTROLE_ECHANTILLON_JUILLET\PONTS   # Destination Esri Shapefile Folder

Readers:
- SQLITE3FDO_1: SQLITE3FDO from $(SourceDataset_SQLITE3FDO) in EPSG:3948

Writers:
- ESRISHAPE_1: ESRISHAPE to $(DestDataset_ESRISHAPE) in EPSG:3948

Default.2047000_7273000_pointspont (reader SQLITE3FDO_1)
    attributes: ogc_fid int64, location char(255), srs char(255), modified char(255), created char(255)
    -> Deaggregator
    -> AttributeCreator
AttributeCreator
    ATTR_TABLE = SET_TO mergeid = 1
    -> FeatureMerger [SUPPLIER]
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator
AreaCalculator
    AREA_ATTR = _area
    AREA_TYPE = Plane Area
    MULT = 1
    -> Tester
Tester
    BOOL_OP = OR
    TEST_CLAUSE = TEST @Value(_area) >= 10
    FAILED -> AttributeCreator_2
AttributeCreator_2
    ATTR_TABLE = SET_TO mergeid = 1
    -> FeatureMerger [REQUESTOR]
FeatureMerger
    ATTR_ACCUM_MODE = Merge Supplier
    ATTR_CONFLICT_RES = Use Supplier
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> StringConcatenator
StringConcatenator
    ACTION = Create New Attribute
    PARM_LINE = @Value(fme_basename)_PontsInf10m2
    VAL_ATTR = NomFichier
    -> Default.2047000_7273000_pointspont (writer ESRISHAPE_1)
Default.2047000_7273000_pointspont (writer ESRISHAPE_1)
