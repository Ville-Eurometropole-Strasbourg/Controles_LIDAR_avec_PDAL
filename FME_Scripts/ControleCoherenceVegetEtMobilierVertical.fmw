FME workspace ControleCoherenceVegetEtMobilierVertical.fmw

Parameters:
- SourceDataset_SQLITE3FDO_3 = S:\Commun\SIG3D\2020\PROJETS_2020\20019_LIDAR_2020\03_REALISATION\01_CONTROLES\CONTROLE_ECHANTILLON_JUILLET\VEGET\2047000_7285000_ContourVegetHAGSup3m.sqlite   # SQLite3 Spatial (FDO) Database
- FEATURE_TYPES =
- SourceDataset_ESRISHAPE = ""S:\Commun\SIG3D\2020\PROJETS_2020\20019_LIDAR_2020\03_REALISATION\DATA_4_ATGT\EMS\TOPO\EMS_Lampadaires.shp" "S:\Commun\SIG3D\2020\PROJETS_2020\20019_LIDAR_2020\03_REALISATION\DATA_4_ATGT\EMS\TOPO\EMS_PoteauDirectionnel.shp" "S:\Commun\SIG3D\2020\PROJETS_2020\20019_LIDAR_2020\03_REALISATION\DATA_4_ATGT\EMS\TOPO\EMS_Poteaux.shp" "S:\Commun\SIG3D\2020\PROJETS_2020\20019_LIDAR_2020\03_REALISATION\DATA_4_ATGT\EMS\TOPO\EMS_Poteaux_Catenaires.shp" "S:\Commun\SIG3D\2020\PROJETS_2020\20019_LIDAR_2020\03_REALISATION\DATA_4_ATGT\EMS\TOPO\EMS_Poteaux_Feu_circulation.shp" "S:\Commun\SIG3D\2020\PROJETS_2020\20019_LIDAR_2020\03_REALISATION\DATA_4_ATGT\EMS\TOPO\EMS_Pylones.shp""   # Source Esri Shapefile(s)
- DestDataset_ESRISHAPE = S:\Commun\SIG3D\2020\PROJETS_2020\20019_LIDAR_2020\03_REALISATION\01_CONTROLES\CONTROLE_ECHANTILLON_JUILLET\VEGET   # Destination Esri Shapefile Folder
- SourceDataset_ESRISHAPE_3 = S:\Commun\SIG3D\2020\PROJETS_2020\20019_LIDAR_2020\03_REALISATION\01_CONTROLES\DATA_SIG\BD200_rg_amg_arbre.shp   # Source Esri Shapefile(s)
- DestDataset_ESRISHAPE_2 = S:\Commun\SIG3D\2020\PROJETS_2020\20019_LIDAR_2020\03_REALISATION\01_CONTROLES\CONTROLE_ECHANTILLON_JUILLET\VEGET   # Destination Esri Shapefile Folder

Readers:
- SQLITE3FDO_1: SQLITE3FDO from $(SourceDataset_SQLITE3FDO_3) in EPSG:3948
- ESRISHAPE_1: ESRISHAPE from $(SourceDataset_ESRISHAPE) in EPSG:3948
- ESRISHAPE_2: ESRISHAPE from $(SourceDataset_ESRISHAPE_3) in EPSG:3948

Writers:
- ESRISHAPE_3: ESRISHAPE to $(DestDataset_ESRISHAPE) in EPSG:3948
- ESRISHAPE_4: ESRISHAPE to $(DestDataset_ESRISHAPE_2) in EPSG:3948

Default.2047000_7273000_pointsveget (reader SQLITE3FDO_1)
    attributes: ogc_fid int64, location char(255), srs char(255), modified char(255), created char(255)
    -> Deaggregator
    -> BoundingBoxReplacer
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator
AreaCalculator
    AREA_ATTR = _area
    AREA_TYPE = Plane Area
    MULT = 1
    -> Tester_2
    -> AttributeCreator
Note: surface veget supérieure à 5m²
Tester_2
    BOOL_OP = OR
    TEST_CLAUSE = TEST @Value(_area) > 5
    PASSED -> NeighborFinder_2 [BASE]
    FAILED -> NeighborFinder_2 [BASE]
    FAILED -> NeighborFinder_3 [BASE]
AttributeCreator
    ATTR_TABLE = SET_TO mergeid = 1
    -> NeighborFinder_4 [CANDIDATE]
    -> FeatureMerger [SUPPLIER]
BoundingBoxReplacer
    BOXTYPE = Bounding Box
    BOX -> Clipper [CLIPPER]
BD200_rg_amg_arbre (reader ESRISHAPE_2)
    attributes: gid long, ident_gy number(20,0), diametre char(254), code_preci char(254), date_leve char(20), auteur char(254), date_reco char(20), angle_g number(31,15), z_sol number(31,15), date_creat char(20), date_maj char(20)
    -> NeighborFinder_3 [CANDIDATE]
    -> Clipper [CLIPPEE]
NeighborFinder_3
    CANDIDATES_FIRST = No
    INSERT_VERTEX = No
    K = 1
    MAX = 1
    MEASURES_FROM_CANDIDATE = No
    MODE = Bases and Candidates
    TREAT_POLYGON_AS = Areas
    UNMATCHED_BASE -> NeighborFinder [BASE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> NeighborFinder_4 [BASE]
NeighborFinder_4
    CANDIDATES_FIRST = No
    INSERT_VERTEX = No
    K = 1
    MAX = 1
    MEASURES_FROM_CANDIDATE = No
    MODE = Bases and Candidates
    TREAT_POLYGON_AS = Areas
    UNMATCHED_BASE -> AttributeCreator_2
AttributeCreator_2
    ATTR_TABLE = SET_TO mergeid = 1
    -> FeatureMerger [REQUESTOR]
FeatureMerger
    ATTR_ACCUM_MODE = Merge Supplier
    ATTR_CONFLICT_RES = Use Supplier
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = @Value(fme_basename)_ArbreBDSansLidar3m
    VAL_ATTR = NomFichier
    -> Shapefile1 (writer ESRISHAPE_4)
Shapefile1 (writer ESRISHAPE_4)
    attributes: mergeid char(200), gid char(200), ident_gy char(200), diametre char(200), code_preci char(200), date_leve char(200), auteur char(200), date_reco char(200), angle_g char(200), z_sol char(200), date_creat char(200), date_maj char(200), _clipped char(200), ogc_fid number(20,0), location char(255), srs char(255), modified char(255), created char(255), _hierarchy char(200), _geometry_ char(200), _hierarc00 char(200), _hierarc01 char(200), _part_numb char(200), _area char(200), NomFichier char(200)
EMS_Lampadaires (reader ESRISHAPE_1)
    attributes: EMS_Lam_ID long
    -> NeighborFinder [CANDIDATE]
EMS_PoteauDirectionnel (reader ESRISHAPE_1)
    attributes: EMS_Pot_ID long
    -> NeighborFinder [CANDIDATE]
EMS_Poteaux_Feu_circulation (reader ESRISHAPE_1)
    attributes: EMS_Pot_ID long
    -> NeighborFinder [CANDIDATE]
EMS_Poteaux (reader ESRISHAPE_1)
    attributes: EMS_Pot_ID long
    -> NeighborFinder [CANDIDATE]
EMS_Poteaux_Catenaires (reader ESRISHAPE_1)
    attributes: EMS_Pot_ID long
    -> NeighborFinder [CANDIDATE]
NeighborFinder
    CANDIDATES_FIRST = No
    INSERT_VERTEX = No
    K = 1
    MAX = 2
    MEASURES_FROM_CANDIDATE = No
    MODE = Bases and Candidates
    TREAT_POLYGON_AS = Areas
    MATCHED -> StringConcatenator
EMS_Pylones (reader ESRISHAPE_1)
    attributes: EMS_Pyl_ID long
    -> NeighborFinder_2 [CANDIDATE]
NeighborFinder_2
    CANDIDATES_FIRST = No
    INSERT_VERTEX = No
    K = 1
    MAX = 2
    MEASURES_FROM_CANDIDATE = No
    MODE = Bases and Candidates
    TREAT_POLYGON_AS = Areas
    MATCHED -> StringConcatenator
StringConcatenator
    ACTION = Create New Attribute
    PARM_LINE = @Value(fme_basename)_VerifCoherenceVegetMobVertical
    VAL_ATTR = NomFichier
    -> EMS_Pylones (writer ESRISHAPE_3)
EMS_Pylones (writer ESRISHAPE_3)
