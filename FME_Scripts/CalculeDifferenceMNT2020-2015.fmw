FME workspace CalculeDifferenceMNT2020-2015.fmw

Parameters:
- SourceDataset_TIFF = S:\Commun\SIG3D\2020\PROJETS_2020\20019_LIDAR_2020\03_REALISATION\01_CONTROLES\TRAVAIL\RASTER\MNT_SOL_TROUS_2020\2047000_7285000_MNRaster2020.tif   # Source TIFF (Tagged Image File Format) File(s)
- SourceDataset_TIFF_3 = S:\Commun\SIG3D\2020\PROJETS_2020\20019_LIDAR_2020\03_REALISATION\01_CONTROLES\TRAVAIL\RASTER\MNT_SOL_TROUS_2015\2047000_7285000_MNTRaster2015.tif   # Source TIFF (Tagged Image File Format) File(s)
- DestDataset_GEOTIFF = S:\Commun\SIG3D\2020\PROJETS_2020\20019_LIDAR_2020\03_REALISATION\01_CONTROLES\TRAVAIL\RASTER\MNT_SOL_COMPARAISON20152020   # Destination GeoTIFF Folder
- DestDataset_SQLITE3FDO = S:\Commun\SIG3D\2020\PROJETS_2020\20019_LIDAR_2020\03_REALISATION\01_CONTROLES\TRAVAIL\RASTER\MNT_SOL_COMPARAISON20152020\2047000_7273000_DifferenceMNT2020-2015.sqlite   # SQLite3 Spatial (FDO) Database
- DestDataset_ESRISHAPE = S:\Commun\SIG3D\2020\PROJETS_2020\20019_LIDAR_2020\03_REALISATION\01_CONTROLES\TRAVAIL\RASTER\MNT_SOL_COMPARAISON20152020   # Destination Esri Shapefile Folder

Readers:
- TIFF_1: TIFF from $(SourceDataset_TIFF) in EPSG:3948
- TIFF_2: TIFF from $(SourceDataset_TIFF_3) in EPSG:3948

Writers:
- GEOTIFF_1: GEOTIFF to $(DestDataset_GEOTIFF) in EPSG:3948
- SQLITE3FDO_1: SQLITE3FDO to $(DestDataset_SQLITE3FDO) in EPSG:3948
- ESRISHAPE_1: ESRISHAPE to $(DestDataset_ESRISHAPE) in EPSG:3948

Note: TIFF: 2047000_7273000_MNTRaster2020 [TIFF]
TIFF (reader TIFF_1)
    -> RasterCellValueCalculator [A]
Note: TIFF: 2047000_7273000_MNTRaster2015 [TIFF]
TIFF (reader TIFF_2)
    -> RasterCellValueCalculator [B]
RasterCellValueCalculator
    ACCUMULATE_ATTRIBUTES = Yes
    OPERATION = -
    PRESERVE_INTERPRETATION = Yes
    -> StringReplacer
StringReplacer
    CASE = NO
    FIND_TEXT = MNTRaster2015
    NO_MATCH = _FME_NO_OP_
    REGEXP = NO
    REPLACE_TEXT = DifferenceMNT2020-2015
    SRC_ATTRS = fme_basename
    -> Raster1 (writer GEOTIFF_1)
    -> RasterCellValueReplacer [off]
Raster1 (writer GEOTIFF_1)
RasterCellValueReplacer
    NEW_VALUE = 30
    REPLACE_GREATER_THAN = 1
    REPLACE_LESS_THAN = -1
    REPLACE_NODATA = No
    -> RasterCellValueReplacer_2
RasterCellValueReplacer_2
    NEW_VALUE = -9999
    REPLACE_GREATER_THAN = -1
    REPLACE_LESS_THAN = 1
    REPLACE_NODATA = No
    -> RasterToPolygonCoercer
RasterToPolygonCoercer
    EXTRACT_NODATA = No
    LABEL_ATTRIBUTE = _label
    PRESERVE_ATTRIBUTES = Yes
    POLYGONS -> Difference20202015 (writer SQLITE3FDO_1)
    POLYGONS -> Shapefile1 (writer ESRISHAPE_1)
Difference20202015 (writer SQLITE3FDO_1) [off]
    attributes: _label char(200)
Shapefile1 (writer ESRISHAPE_1) [off]
    attributes: _label char(200)
