FME workspace IdentifieIDBandedeVol.fmw

Parameters:
- SourceDataset_LAS = ""S:\Commun\SIG3D\2020\PROJETS_2020\20019_LIDAR_2020\03_REALISATION\01_CONTROLES\CONTROLE_ECHANTILLON_JUILLET\SPILT_ID\2047000_7285000_1.laz" "S:\Commun\SIG3D\2020\PROJETS_2020\20019_LIDAR_2020\03_REALISATION\01_CONTROLES\CONTROLE_ECHANTILLON_JUILLET\SPILT_ID\2047000_7285000_2.laz" "S:\Commun\SIG3D\2020\PROJETS_2020\20019_LIDAR_2020\03_REALISATION\01_CONTROLES\CONTROLE_ECHANTILLON_JUILLET\SPILT_ID\2047000_7285000_3.laz" "S:\Commun\SIG3D\2020\PROJETS_2020\20019_LIDAR_2020\03_REALISATION\01_CONTROLES\CONTROLE_ECHANTILLON_JUILLET\SPILT_ID\2047000_7285000_4.laz""   # Source ASPRS LAS File(s)
- FEATURE_TYPES =   # LAS Feature Types to Read
- DestDataset_LAS = S:\Commun\SIG3D\2020\PROJETS_2020\20019_LIDAR_2020\03_REALISATION\01_CONTROLES\CONTROLE_ECHANTILLON_JUILLET\SPILT_ID\ID   # Destination ASPRS LAS Folder

Readers:
- LAS_1: LAS from $(SourceDataset_LAS) in EPSG:3948

Writers:
- LAS_2: LAS to $(DestDataset_LAS) in EPSG:3948

LAS (reader LAS_1)
    -> Counter
Counter
    CNT_ATTR = _count
    DOMAIN = counter
    SCOPE = Global
    START = 0
    -> FeatureMerger [REQUESTOR]
    -> PointCloudThinner
PointCloudThinner
    MAX_NUM_POINTS = 1
    THINNED -> PointCloudCoercer
PointCloudCoercer
    ACCUM_ATTRS_NAME = Yes
    CONVERT_TO_DISPLAY = Individual Points
    PART_NUMBER_ATTR_NAME = _part_number
    POINT_COMPONENTS = gps_time intensity classification return number_of_returns angle scan_direction point_source_id
    POINT_COMPONENTS_PRESERVE_DISPLAY = Measures
    COERCED -> MeasureExtractor
MeasureExtractor
    GEOM_TYPE = Point
    MEASURE_ATTR = point_source_id
    MEASURE_NAME = point_source_id
    -> SubstringExtractor
SubstringExtractor
    END = -3
    RESULT_ATTR = _substring
    SRC_STRING = @Value(fme_basename)
    START = 0
    -> StringConcatenator
StringConcatenator
    ACTION = Create New Attribute
    PARM_LINE = @Value(point_source_id)_@Value(_substring)
    VAL_ATTR = NomFichier
    -> FeatureMerger [SUPPLIER]
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> PointCloudCombiner
PointCloudCombiner
    ACCUM_ATTRS_NAME = Yes
    EXTRACT_RASTER_NODATA_NAME = No
    GROUP_BY = point_source_id
    SPACING = 1.0
    -> LAS (writer LAS_2)
LAS (writer LAS_2)
