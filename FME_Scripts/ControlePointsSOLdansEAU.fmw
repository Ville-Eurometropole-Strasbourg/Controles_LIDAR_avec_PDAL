FME workspace ControlePointsSOLdansEAU.fmw

Parameters:
- SourceDataset_LAS = S:\Commun\SIG3D\2020\PROJETS_2020\20019_LIDAR_2020\03_REALISATION\01_CONTROLES\CONTROLE_ECHANTILLON_JUILLET\LIDAR_ECHANTILLON_ORIGINAL\2047000_7285000\2047000_7285000_Lidar2020NoColor.las   # Source ASPRS LAS File(s)
- SourceDataset_ESRISHAPE = S:\Commun\SIG3D\2020\PROJETS_2020\20019_LIDAR_2020\03_REALISATION\01_CONTROLES\DATA_SIG\Surfaces_EAU.shp   # Source Esri Shapefile(s)
- DestDataset_LAS = S:\Commun\SIG3D\2020\PROJETS_2020\20019_LIDAR_2020\03_REALISATION\01_CONTROLES\CONTROLE_ECHANTILLON_JUILLET\EAU   # Destination ASPRS LAS Folder

Readers:
- LAS_1: LAS from $(SourceDataset_LAS) in EPSG:3948
- ESRISHAPE_1: ESRISHAPE from $(SourceDataset_ESRISHAPE) in EPSG:3948

Writers:
- LAS_2: LAS to $(DestDataset_LAS) in EPSG:3948

LAS (reader LAS_1)
    -> PointCloudSplitter
PointCloudSplitter
    OUTPUT_ATTR = _split_value
    SPLIT_BY_DISPLAY = classification
    SPLIT_TYPE = Unique
    VALUE_LIST = 2
    SPLIT -> Clipper [CLIPPEE]
    SPLIT -> BoundingBoxReplacer
BoundingBoxReplacer
    BOXTYPE = Bounding Box
    BOX -> AttributeCreator
AttributeCreator
    ATTR_TABLE = SET_TO idmerge = 1
    -> FeatureMerger [SUPPLIER]
Surfaces_EAU (reader ESRISHAPE_1)
    attributes: Surface_ID long
    -> GeometryCoercer
GeometryCoercer
    GQUERY:
      for $geom in //geometry
      where $geom/count(parent::geometry) = 0
      return number($geom/@fme_id)
    KIND = fme_polygon
    COERCED -> DonutBuilder
DonutBuilder
    ALLOW_CYCLES = No
    CONNECT_Z_MODE = First Wins
    DROP = yes
    AREA -> Clipper [CLIPPER]
    AREA -> NeighborFinder [CANDIDATE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> PointCloudCoercer
PointCloudCoercer
    ACCUM_ATTRS_NAME = Yes
    CONVERT_TO_DISPLAY = Individual Points
    PART_NUMBER_ATTR_NAME = _part_number
    POINT_COMPONENTS_PRESERVE_DISPLAY = Attributes
    COERCED -> NeighborFinder [BASE]
NeighborFinder
    CANDIDATES_FIRST = No
    INSERT_VERTEX = No
    K = 1
    MAX = 2
    MEASURES_FROM_CANDIDATE = No
    MODE = Bases and Candidates
    TREAT_POLYGON_AS = Lines
    UNMATCHED_BASE -> PointCloudCombiner
PointCloudCombiner
    ACCUM_ATTRS_NAME = Yes
    EXTRACT_RASTER_NODATA_NAME = No
    SPACING = 1.0
    -> AttributeCreator_2
AttributeCreator_2
    ATTR_TABLE = SET_TO idmerge = 1
    -> FeatureMerger [REQUESTOR]
FeatureMerger
    ATTR_ACCUM_MODE = Merge Supplier
    ATTR_CONFLICT_RES = Use Supplier
    IGNORE_NULLS = No
    JOIN_KEYS = @Value(idmerge) @Value(idmerge) AUTO
    MERGE_TYPE = Attributes Only
    PROCESS_DUPS = NO
    REJECT_NULL_MISSING_KEYS = No
    SUPPLIERS_FIRST = No
    MERGED -> StringConcatenator
StringConcatenator
    ACTION = Create New Attribute
    PARM_LINE = @Value(fme_basename)_PointsSOLdansEAU
    VAL_ATTR = NomFichier
    -> LAS (writer LAS_2)
LAS (writer LAS_2)
