FME workspace IdentifieStockageATrousOuPetit.fmw

Parameters:
- SourceDataset_SQLITE3FDO = S:\Commun\SIG3D\2020\PROJETS_2020\20019_LIDAR_2020\03_REALISATION\01_CONTROLES\LAS_HAG\ContourPonts.sqlite   # SQLite3 Spatial (FDO) Database
- DestDataset_ESRISHAPE = S:\Commun\SIG3D\2020\PROJETS_2020\20019_LIDAR_2020\03_REALISATION\01_CONTROLES\LAS_HAG   # Destination Esri Shapefile Folder

Readers:
- SQLITE3FDO_1: SQLITE3FDO from $(SourceDataset_SQLITE3FDO) in EPSG:3948

Writers:
- ESRISHAPE_1: ESRISHAPE to $(DestDataset_ESRISHAPE) in EPSG:3948

Default.pointsponts (reader SQLITE3FDO_1)
    attributes: ogc_fid int64, location char(255), srs char(255), modified char(255), created char(255)
    -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> HoleCounter
HoleCounter
    CNT_ATTR = _hole_count
    -> Tester
Tester
    BOOL_OP = OR
    TEST_CLAUSE = TEST @Value(_hole_count) > 0
    PASSED -> StockageAvecTrouOuInf25m2 (writer ESRISHAPE_1)
    FAILED -> AreaCalculator
AreaCalculator
    AREA_ATTR = _area
    AREA_TYPE = Plane Area
    MULT = 1
    -> Tester_2
Tester_2
    BOOL_OP = OR
    TEST_CLAUSE = TEST @Value(_area) <= 25
    PASSED -> StockageAvecTrouOuInf25m2 (writer ESRISHAPE_1)
    FAILED -> StockageCriteresOK (writer ESRISHAPE_1)
StockageAvecTrouOuInf25m2 (writer ESRISHAPE_1)
StockageCriteresOK (writer ESRISHAPE_1)
