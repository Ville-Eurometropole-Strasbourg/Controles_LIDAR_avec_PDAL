FME workspace CalculMNTSOL_FME.fmw

Parameters:
- DestDataset_GEOTIFF = S:\Commun\SIG3D\2020\PROJETS_2020\20019_LIDAR_2020\03_REALISATION\01_CONTROLES\CONTROLE_ECHANTILLON_JUILLET\ISOLE   # Destination GeoTIFF Folder
- SourceDataset_TIFF = S:\Commun\SIG3D\2020\PROJETS_2020\20019_LIDAR_2020\03_REALISATION\01_CONTROLES\CONTROLE_ECHANTILLON_JUILLET\ISOLE\2047000_7285000_MNTMAX.tif   # Source TIFF (Tagged Image File Format) File(s)

Readers:
- TIFF_1: TIFF from $(SourceDataset_TIFF) in EPSG:3948

Writers:
- GEOTIFF_1: GEOTIFF to $(DestDataset_GEOTIFF) in EPSG:3948

TIFF (reader TIFF_1)
    -> RasterDEMGenerator [POINTS/LINES]
    -> BoundingBoxReplacer
RasterDEMGenerator
    INTERPOLATION_TYPE = AUTO
    NODATA_VALUE = -9999
    TOLERANCE = 0
    X_SPACING = 0.5
    Y_SPACING = 0.5
    DEM_RASTER -> AttributeCreator_2
AttributeCreator_2
    ATTR_TABLE = SET_TO idmerge = 1
    -> FeatureMerger [REQUESTOR]
BoundingBoxReplacer
    BOXTYPE = Bounding Box
    BOX -> AttributeCreator
AttributeCreator
    ATTR_TABLE = SET_TO idmerge = 1
    -> FeatureMerger [SUPPLIER]
FeatureMerger
    ATTR_ACCUM_MODE = Merge Supplier
    ATTR_CONFLICT_RES = Use Supplier
    IGNORE_NULLS = No
    JOIN_KEYS = @Value(idmerge) @Value(idmerge) AUTO
    MERGE_TYPE = Attributes Only
    PROCESS_DUPS = NO
    REJECT_NULL_MISSING_KEYS = No
    SUPPLIERS_FIRST = No
    MERGED -> StringConcatenator
StringConcatenator
    ACTION = Create New Attribute
    PARM_LINE = @Value(fme_basename)_MNTSOL_FME
    VAL_ATTR = NomFichier
    -> Raster1 (writer GEOTIFF_1)
Raster1 (writer GEOTIFF_1)
    attributes: idmerge char(200), NomFichier char(200)
