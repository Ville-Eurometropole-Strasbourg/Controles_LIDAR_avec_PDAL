FME workspace IdentifiePointsTOITSDansEAU.fmw

Parameters:
- SourceDataset_ESRISHAPE = S:\Commun\SIG3D\2020\PROJETS_2020\20019_LIDAR_2020\03_REALISATION\01_CONTROLES\DATA_SIG\Surfaces_EAU.shp   # Source Esri Shapefile(s)
- SourceDataset_LAS = S:\Commun\SIG3D\2020\PROJETS_2020\20019_LIDAR_2020\03_REALISATION\01_CONTROLES\CONTROLE_ECHANTILLON_JUILLET\LIDAR_ECHANTILLON_ORIGINAL\2047000_7273000_Lidar2020.laz   # Source ASPRS LAS File(s)
- DestDataset_LAS = S:\Commun\SIG3D\2020\PROJETS_2020\20019_LIDAR_2020\03_REALISATION\01_CONTROLES\CONTROLE_ECHANTILLON_JUILLET\TOITS   # Destination ASPRS LAS Folder

Readers:
- ESRISHAPE_1: ESRISHAPE from $(SourceDataset_ESRISHAPE) in EPSG:3948
- LAS_1: LAS from $(SourceDataset_LAS) in EPSG:3948

Writers:
- LAS_2: LAS to $(DestDataset_LAS) in EPSG:3948

Surfaces_EAU (reader ESRISHAPE_1)
    attributes: Surface_ID long
    -> GeometryCoercer
GeometryCoercer
    GQUERY:
      for $geom in //geometry
      where $geom/count(parent::geometry) = 0
      return number($geom/@fme_id)
    KIND = fme_polygon
    COERCED -> DonutBuilder
DonutBuilder
    ALLOW_CYCLES = No
    CONNECT_Z_MODE = First Wins
    DROP = yes
    AREA -> Clipper [CLIPPER]
LAS (reader LAS_1)
    -> PointCloudSplitter
PointCloudSplitter
    OUTPUT_ATTR = _split_value
    SPLIT_BY_DISPLAY = classification
    SPLIT_TYPE = Unique
    VALUE_LIST = 6
    SPLIT -> Clipper [CLIPPEE]
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> PointCloudCombiner
PointCloudCombiner
    ACCUM_ATTRS_NAME = Yes
    EXTRACT_RASTER_NODATA_NAME = No
    SPACING = 1.0
    -> LAS (writer LAS_2)
LAS (writer LAS_2)
