FME workspace DetecteVegetIsoleeMoins3m².fmw

Parameters:
- DestDataset_ESRISHAPE = S:\Commun\SIG3D\2020\PROJETS_2020\20019_LIDAR_2020\03_REALISATION\01_CONTROLES\CONTROLE_ECHANTILLON_JUILLET\VEGET   # Destination Esri Shapefile Folder
- SourceDataset_SQLITE3FDO_4 = S:\Commun\SIG3D\2020\PROJETS_2020\20019_LIDAR_2020\03_REALISATION\01_CONTROLES\CONTROLE_ECHANTILLON_JUILLET\VEGET\2047000_7285000_ContourVeget.sqlite   # SQLite3 Spatial (FDO) Database
- FEATURE_TYPES =
- SourceDataset_SQLITE3FDO = S:\Commun\SIG3D\2020\PROJETS_2020\20019_LIDAR_2020\03_REALISATION\01_CONTROLES\CONTROLE_ECHANTILLON_JUILLET\VEGET\2047000_7285000_ContourVegetHAGSup3m.sqlite   # SQLite3 Spatial (FDO) Database
- FEATURE_TYPES_2 =

Readers:
- SQLITE3FDO_3: SQLITE3FDO from $(SourceDataset_SQLITE3FDO_4) in EPSG:3948
- SQLITE3FDO_1: SQLITE3FDO from $(SourceDataset_SQLITE3FDO) in EPSG:3948

Writers:
- ESRISHAPE_1: ESRISHAPE to $(DestDataset_ESRISHAPE) in EPSG:3948

Default.2047000_7285000_pointsveget (reader SQLITE3FDO_3)
    attributes: ogc_fid int64, location char(255), srs char(255), modified char(255), created char(255)
    -> Deaggregator
    -> AttributeCreator
AttributeCreator
    ATTR_TABLE = SET_TO mergeid = 1
    -> FeatureMerger [SUPPLIER]
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator
AreaCalculator
    AREA_ATTR = _area
    AREA_TYPE = Plane Area
    MULT = 1
    -> Tester
Tester
    BOOL_OP = OR
    TEST_CLAUSE = TEST @Value(_area) <= 3
    PASSED -> AreaOnAreaOverlayer [AREA]
Default.2047000_7285000_vegethagsup3m (reader SQLITE3FDO_1)
    attributes: ogc_fid int64, location char(255), srs char(255), modified char(255), created char(255)
    -> Deaggregator_2
Deaggregator_2
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator_2
AreaCalculator_2
    AREA_ATTR = _area
    AREA_TYPE = Plane Area
    MULT = 1
    -> Tester_2
Tester_2
    BOOL_OP = OR
    TEST_CLAUSE = TEST @Value(_area) <= 3
    PASSED -> AreaOnAreaOverlayer [AREA]
AreaOnAreaOverlayer
    ACCUM_ATTRS_NAME = Use Attributes From One Feature
    CLEANING_TOLERANCE = None
    CONNECT_Z_MODE = First Wins
    DEAGGREGATE_INPUT = Yes
    OVC_ATTR = _overlaps
    AREA -> Tester_3
Tester_3
    BOOL_OP = OR
    TEST_CLAUSE = TEST @Value(_overlaps) > 1
    PASSED -> AttributeCreator_2
AttributeCreator_2
    ATTR_TABLE = SET_TO mergeid = 1
    -> FeatureMerger [REQUESTOR]
FeatureMerger
    ATTR_ACCUM_MODE = Merge Supplier
    ATTR_CONFLICT_RES = Use Supplier
    IGNORE_NULLS = No
    JOIN_KEYS = @Value(mergeid) @Value(mergeid) AUTO
    MERGE_TYPE = Attributes Only
    PROCESS_DUPS = NO
    REJECT_NULL_MISSING_KEYS = No
    SUPPLIERS_FIRST = No
    MERGED -> StringConcatenator
StringConcatenator
    ACTION = Create New Attribute
    PARM_LINE = @Value(fme_basename)_VegetIsole
    VAL_ATTR = NomFichier
    -> Shapefile1 (writer ESRISHAPE_1)
Shapefile1 (writer ESRISHAPE_1)
